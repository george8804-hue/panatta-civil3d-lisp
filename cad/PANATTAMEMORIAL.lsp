;;; PANATTA MEMORIAL 0.1 - Fase 1, leitura somente de LWPOLYLINE.
;;; Carregue com APPLOAD. Requer Windows + pacote do nucleo ao lado deste arquivo.
;;; Nenhum entmod/command de edicao e nenhum setvar e utilizado.
(vl-load-com)
(if (not *panatta-home*)
  (setq *panatta-home*
    (if (findfile "PANATTAMEMORIAL.lsp")
      (vl-filename-directory (findfile "PANATTAMEMORIAL.lsp")) nil)))

(defun pm:fail (message)
  (princ (strcat "\nPANATTA: " message))
  (exit))

(defun pm:json-string (s / result c)
  (setq result "\"")
  (foreach c (vl-string->list s)
    (setq result (strcat result
      (cond ((= c 34) "\\\"") ((= c 92) "\\\\")
            ((< c 32) " ")
            ;; ASCII-only JSON supports Civil 3D 2020 legacy LISP encoding.
            ((> c 65535) (strcat "\\u" (pm:hex4 (+ 55296 (fix (/ (- c 65536) 1024))))
                                      "\\u" (pm:hex4 (+ 56320 (rem (- c 65536) 1024)))))
            ((> c 127) (strcat "\\u" (pm:hex4 c)))
            (t (chr c))))))
  (strcat result "\""))

(defun pm:hex4 (n / s)
  (setq s "")
  (repeat 4
    (setq s (strcat (substr "0123456789abcdef" (1+ (rem n 16)) 1) s)
          n (fix (/ n 16)))) s)

(defun pm:num (x)
  ;; Scientific notation avoids DIMZIN/LUNITS effects without changing sysvars.
  (vl-string-translate "," "." (rtos (float x) 1 16)))

(defun pm:vertices (data / result item current)
  (foreach item data
    (cond ((= (car item) 10)
           (if current (setq result (cons current result)))
           (setq current (list (cadr item) (caddr item) 0.0)))
          ((and current (= (car item) 42))
           (setq current (list (car current) (cadr current) (cdr item))))))
  (if current (setq result (cons current result)))
  (reverse result))

(defun pm:show-vertices (en data / v p elev index)
  (setq index 1 elev (cond ((cdr (assoc 38 data))) (t 0.0)))
  (princ "\nVertices originais, em WCS e na unidade do desenho:")
  (foreach v (pm:vertices data)
    (setq p (trans (list (car v) (cadr v) elev) en 0))
    (princ (strcat "\n" (itoa index) ": E=" (pm:num (car p)) " N=" (pm:num (cadr p))))
    (setq index (1+ index))))

(defun pm:line (text stream)
  (if (null (write-line text stream))
    (pm:fail "Falha ao gravar entrada geometrica.")))

(defun pm:write-input (file en data unit start reversep / f result closing)
  (setq f (open file "w"))
  (if (not f) (pm:fail "Nao foi possivel gravar o JSON de entrada."))
  (setq result (vl-catch-all-apply 'pm:emit-input (list f en data unit start reversep))
        closing (vl-catch-all-apply 'close (list f)))
  (if (or (vl-catch-all-error-p result) (vl-catch-all-error-p closing))
    (progn
      (vl-file-delete file)
      (pm:fail "Falha na exportacao da entrada; arquivo incompleto descartado."))))

(defun pm:emit-input (f en data unit start reversep / verts v p i bulge normal elev area perim)
  (setq verts (pm:vertices data) normal (cdr (assoc 210 data))
        elev (cond ((cdr (assoc 38 data))) (t 0.0)))
  (if (not normal) (setq normal '(0.0 0.0 1.0)))
  (setq area (vl-catch-all-apply 'vlax-curve-getArea (list en))
        perim (vl-catch-all-apply 'vlax-curve-getDistAtParam
                (list en (vlax-curve-getEndParam en))))
  (if (or (vl-catch-all-error-p area) (vl-catch-all-error-p perim))
    (pm:fail "Nao foi possivel ler area/perimetro nativos."))
  (pm:line "{\"schemaVersion\":\"1.0\",\"source\":\"LWPOLYLINE\",\"closed\":true," f)
  (pm:line (strcat "\"drawing\":" (pm:json-string (strcat (getvar "DWGPREFIX") (getvar "DWGNAME")))
    ",\"handle\":" (pm:json-string (cdr (assoc 5 data))) ",") f)
  (pm:line (strcat "\"units\":" (pm:json-string unit) ",\"startVertex\":" (itoa start)
    ",\"reverse\":" (if reversep "true" "false") ",") f)
  (pm:line (strcat "\"nativeArea\":" (pm:num area) ",\"nativePerimeter\":" (pm:num perim) ",\"vertices\":[") f)
  (setq i 0)
  (foreach v verts
    ;; en transforms OCS to WCS, independent of current UCS. Reverse normal flips bulge.
    (setq p (trans (list (car v) (cadr v) elev) en 0)
          bulge (* (caddr v) (if (< (caddr normal) 0) -1.0 1.0)))
    (pm:line (strcat (if (> i 0) "," "") "{\"e\":" (pm:num (car p))
      ",\"n\":" (pm:num (cadr p)) ",\"z\":" (pm:num (caddr p))
      ",\"bulge\":" (pm:num bulge) "}") f)
    (setq i (1+ i)))
  (pm:line "]}" f))

(defun pm:run ( / mode en data normal unit start reversep file prefix exe shell code result)
  (initget "A B")
  (setq mode (getkword "\nPANATTA MEMORIAL [A-Gleba/B-Loteamento] <A>: "))
  (princ "\nFase 1: conferencia geometrica individual comum aos modos A/B. Sem emissao de memorial.")
  (setq en (car (entsel "\nSelecione uma LWPOLYLINE fechada: ")))
  (if (not en) (pm:fail "Selecao cancelada."))
  (setq data (entget en))
  (if (/= (cdr (assoc 0 data)) "LWPOLYLINE") (pm:fail "Tipo nao suportado na Fase 1. Selecione LWPOLYLINE."))
  (if (> (cdr (assoc 90 data)) 10000) (pm:fail "Limite do prototipo: 10.000 vertices."))
  (if (= 0 (logand 1 (cdr (assoc 70 data)))) (pm:fail "Polilinha aberta. O desenho nao sera modificado."))
  (setq normal (cdr (assoc 210 data)))
  (if (and normal (or (> (abs (car normal)) 1e-12) (> (abs (cadr normal)) 1e-12)
    (> (abs (- (abs (caddr normal)) 1.0)) 1e-12)))
      (pm:fail "Plano inclinado nao suportado. Necessario plano paralelo a WCS XY."))
  (if (or (and (assoc 43 data) (/= 0.0 (cdr (assoc 43 data))))
    (vl-some '(lambda (pair) (and (member (car pair) '(40 41)) (/= 0.0 (cdr pair)))) data))
      (pm:fail "Polilinha com largura nao suportada na Fase 1."))
  (princ (strcat "\nINSUNITS do desenho: " (itoa (getvar "INSUNITS")) ". Confirme a unidade efetiva; CRS nao e inferido."))
  (initget 1 "Metros Milimetros Centimetros Pes Polegadas PesUS")
  (setq unit (getkword "\nUnidade [Metros/Milimetros/Centimetros/Pes/Polegadas/PesUS]: "))
  (setq unit (cdr (assoc unit '(("Metros" . "m") ("Milimetros" . "mm") ("Centimetros" . "cm")
    ("Pes" . "ft") ("Polegadas" . "in") ("PesUS" . "us-ft")))))
  (princ (strcat "\nVertices: " (itoa (cdr (assoc 90 data))) ". Indice segue a ordem original da entidade."))
  (pm:show-vertices en data)
  (initget 6) (setq start (getint "\nIndice do vertice inicial <1>: "))
  (if (not start) (setq start 1))
  (if (> start (cdr (assoc 90 data))) (pm:fail "Indice inicial fora do intervalo."))
  (initget "Sim Nao") (setq reversep (= "Sim" (getkword "\nInverter sentido original? [Sim/Nao] <Nao>: ")))
  (setq file (getfiled "Salvar entrada geometrica (use nome novo)" (strcat (getvar "DWGPREFIX") "panatta-contorno.json") "json" 1))
  (if (not file) (pm:fail "Saida cancelada."))
  ;; Never replace even if the file dialog's overwrite prompt was accepted.
  (if (findfile file) (pm:fail "Entrada ja existe. Escolha outro nome para preservar a auditoria."))
  (setq prefix (strcat (vl-filename-directory file) "\\" (vl-filename-base file)))
  (if (vl-some 'findfile (list (strcat prefix ".result.json") (strcat prefix ".segments.csv") (strcat prefix ".report.txt")))
    (pm:fail "Relatorios com esse nome ja existem. Escolha outro nome."))
  (pm:write-input file en data unit start reversep)
  (princ (strcat "\nEntrada salva: " file))
  (setq exe (if *panatta-home* (strcat *panatta-home* "\\engine\\Panatta.Cli.exe") nil))
  (if (and exe (findfile exe))
    (progn
      (setq shell (vlax-create-object "WScript.Shell"))
      (setq result (vl-catch-all-apply 'vlax-invoke-method
        (list shell 'Run (strcat "\"" exe "\" --input \"" file "\" --output \"" prefix "\"") 0 :vlax-true)))
      (vlax-release-object shell)
      (if (vl-catch-all-error-p result)
        (princ "\nNao foi possivel executar o nucleo. Use a CLI manualmente conforme README.")
        (progn
          (setq code result)
          (princ (strcat "\nNucleo terminou com codigo " (itoa code) ": 0=geometria conferida; 2=invalida; 3=erro de entrada/arquivo."))
          (if (findfile (strcat prefix ".report.txt"))
            (princ (strcat "\nConfira: " prefix ".report.txt"))
            (princ "\nRelatorio ausente. Execute a CLI no terminal para obter o diagnostico.")))))
    (princ "\nNucleo nao encontrado em engine/Panatta.Cli.exe. Entrada preservada; execute CLI conforme README.")))

(defun c:PANATTAMEMORIAL ( / result)
  (setq result (vl-catch-all-apply 'pm:run nil))
  (if (vl-catch-all-error-p result)
    (princ (strcat "\nPANATTA: " (vl-catch-all-error-message result))))
  (princ))
(princ "\nPANATTA MEMORIAL Fase 1 carregado. Comando: PANATTAMEMORIAL.")
(princ)
